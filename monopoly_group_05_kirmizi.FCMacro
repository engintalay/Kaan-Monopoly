# =============================================================
# MONOPOLY TÜRKİYE - Grup 05: KIRMIZI (Antik Çağ Başkentleri)
# Troya | Bergama | Sardes
# FreeCad Macro - Macro > Execute Macro ile çalıştırın
# =============================================================

import FreeCAD, Part, FreeCADGui, os

W, D, H     = 40.0, 40.0, 4.0
SW, SD, SH  = 40.0, 8.0, 6.0
NECK_W  = 8.0
NECK_D  = 5.0
HEAD_R  = 5.5
TAB_TOL = 0.2

GROUP_COLOR = (0.9, 0.1, 0.1)  # Kırmızı

PROPERTIES = [
    {
        "name": "Troya", "label": "Troya",
        "konum": "Çanakkale", "fiyat": 220,
        "kiralar": [18, 90, 250, 700, 875, 1050], "ipotek": 110, "ev_maliyeti": 150,
    },
    {
        "name": "Bergama", "label": "Bergama",
        "konum": "İzmir", "fiyat": 220,
        "kiralar": [18, 90, 250, 700, 875, 1050], "ipotek": 110, "ev_maliyeti": 150,
    },
    {
        "name": "Sardes", "label": "Sardes",
        "konum": "Manisa", "fiyat": 240,
        "kiralar": [20, 100, 300, 750, 925, 1100], "ipotek": 120, "ev_maliyeti": 150,
    },
]

doc = FreeCAD.newDocument("MonopolyGrup05_Kirmizi")


def make_tile_shape():
    base  = Part.makeBox(W, D, H)
    strip = Part.makeBox(SW, SD, SH)
    strip.translate(FreeCAD.Vector(0, D - SD, H))

    # Puzzle dişi: sağ yüzden (+X) çıkar, komşu kareye kilitlenir
    neck_t = Part.makeBox(NECK_D, NECK_W, H)
    neck_t.translate(FreeCAD.Vector(W, (D - NECK_W) / 2, 0))
    head_t = Part.makeCylinder(HEAD_R, H)
    head_t.translate(FreeCAD.Vector(W + NECK_D, D / 2, 0))
    tab = neck_t.fuse(head_t)

    # Puzzle yuvası: sol yüzden içeri girer, sol komşunun dişini alır
    neck_b = Part.makeBox(NECK_D + TAB_TOL, NECK_W + 2 * TAB_TOL, H)
    neck_b.translate(FreeCAD.Vector(0, (D - NECK_W) / 2 - TAB_TOL, 0))
    head_b = Part.makeCylinder(HEAD_R + TAB_TOL, H)
    head_b.translate(FreeCAD.Vector(NECK_D, D / 2, 0))
    blank = neck_b.fuse(head_b)

    return base.fuse(strip).fuse(tab).cut(blank)


for i, prop in enumerate(PROPERTIES):
    tile = make_tile_shape()
    tile.translate(FreeCAD.Vector(i * (W + 5), 0, 0))

    obj = doc.addObject("Part::Feature", f"Kirmizi_{i+1:02d}_{prop['name']}")
    obj.Shape = tile
    obj.ViewObject.ShapeColor  = GROUP_COLOR
    obj.ViewObject.DisplayMode = "Shaded"

doc.recompute()
FreeCADGui.activeDocument().activeView().viewIsometric()
FreeCADGui.SendMsgToActiveView("ViewFit")
doc.saveAs(os.path.expanduser("~/monopoly_group_05_kirmizi.FCStd"))
print("✅ Grup 05 KIRMIZI tamamlandı: Troya, Bergama, Sardes")

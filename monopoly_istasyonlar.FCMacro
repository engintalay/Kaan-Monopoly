# =============================================================
# MONOPOLY TÜRKİYE - İstasyonlar (Türkiye'nin Büyük Camileri)
# Süleymaniye | Selimiye | Eyüp Sultan | Bursa Ulu Camii
# Her biri: 200₺, kira: 1=25, 2=50, 3=100, 4=200
# FreeCad Macro - Macro > Execute Macro ile çalıştırın
# =============================================================

import FreeCAD, Part, FreeCADGui, os

W, D, H  = 40.0, 40.0, 4.0
NECK_W  = 8.0
NECK_D  = 5.0
HEAD_R  = 5.5
TAB_TOL = 0.2

ISTASYON_COLOR = (0.5, 0.5, 0.5)  # Gri

ISTASYONLAR = [
    {"name": "Suleymaniye",  "label": "Süleymaniye",   "konum": "İstanbul", "fiyat": 200},
    {"name": "Selimiye",     "label": "Selimiye",       "konum": "Edirne",   "fiyat": 200},
    {"name": "EyupSultan",   "label": "Eyüp Sultan",    "konum": "İstanbul", "fiyat": 200},
    {"name": "BursaUluCami", "label": "Bursa Ulu Cami", "konum": "Bursa",    "fiyat": 200},
]

doc = FreeCAD.newDocument("MonopolyIstasyonlar")


def make_tile_shape():
    base = Part.makeBox(W, D, H)

    # Puzzle dişi: sağ yüzden (+X) çıkar
    neck_t = Part.makeBox(NECK_D, NECK_W, H)
    neck_t.translate(FreeCAD.Vector(W, (D - NECK_W) / 2, 0))
    head_t = Part.makeCylinder(HEAD_R, H)
    head_t.translate(FreeCAD.Vector(W + NECK_D, D / 2, 0))
    tab = neck_t.fuse(head_t)

    # Puzzle yuvası: sol yüzden içeri girer
    neck_b = Part.makeBox(NECK_D + TAB_TOL, NECK_W + 2 * TAB_TOL, H)
    neck_b.translate(FreeCAD.Vector(0, (D - NECK_W) / 2 - TAB_TOL, 0))
    head_b = Part.makeCylinder(HEAD_R + TAB_TOL, H)
    head_b.translate(FreeCAD.Vector(NECK_D, D / 2, 0))
    blank = neck_b.fuse(head_b)

    return base.fuse(tab).cut(blank)


for i, ist in enumerate(ISTASYONLAR):
    tile = make_tile_shape()
    tile.translate(FreeCAD.Vector(i * (W + 5), 0, 0))

    obj = doc.addObject("Part::Feature", f"Istasyon_{i+1:02d}_{ist['name']}")
    obj.Shape = tile
    obj.ViewObject.ShapeColor  = ISTASYON_COLOR
    obj.ViewObject.DisplayMode = "Shaded"

doc.recompute()
FreeCADGui.activeDocument().activeView().viewIsometric()
FreeCADGui.SendMsgToActiveView("ViewFit")
doc.saveAs(os.path.expanduser("~/monopoly_istasyonlar.FCStd"))
print("✅ İstasyonlar tamamlandı: Süleymaniye, Selimiye, Eyüp Sultan, Bursa Ulu Cami")

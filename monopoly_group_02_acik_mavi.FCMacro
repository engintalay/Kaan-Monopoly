# =============================================================
# MONOPOLY TÜRKİYE - Grup 02: AÇIK MAVİ (Antik Liman Kentleri)
# Aspendos | Perge | Side
# FreeCad Macro - Macro > Execute Macro ile çalıştırın
# =============================================================

import FreeCAD, Part, FreeCADGui, os

W, D, H     = 40.0, 40.0, 4.0
SW, SD, SH  = 40.0, 8.0, 6.0
NECK_W  = 8.0
NECK_D  = 5.0
HEAD_R  = 5.5
TAB_TOL = 0.2

GROUP_COLOR = (0.4, 0.7, 1.0)  # Açık Mavi

PROPERTIES = [
    {
        "name": "Aspendos", "label": "Aspendos",
        "konum": "Antalya", "fiyat": 100,
        "kiralar": [6, 30, 90, 270, 400, 550], "ipotek": 50, "ev_maliyeti": 50,
    },
    {
        "name": "Perge", "label": "Perge",
        "konum": "Antalya", "fiyat": 100,
        "kiralar": [6, 30, 90, 270, 400, 550], "ipotek": 50, "ev_maliyeti": 50,
    },
    {
        "name": "Side", "label": "Side",
        "konum": "Antalya", "fiyat": 120,
        "kiralar": [8, 40, 100, 300, 450, 600], "ipotek": 60, "ev_maliyeti": 50,
    },
]

doc = FreeCAD.newDocument("MonopolyGrup02_AcikMavi")


def make_tile_shape():
    base  = Part.makeBox(W, D, H)
    strip = Part.makeBox(SW, SD, SH)
    strip.translate(FreeCAD.Vector(0, D - SD, H))

    # Puzzle dişi: sağ yüzden (+X) çıkar, komşu kareye kilitlenir
    neck_t = Part.makeBox(NECK_D, NECK_W, H)
    neck_t.translate(FreeCAD.Vector(W, (D - NECK_W) / 2, 0))
    head_t = Part.makeCylinder(HEAD_R, H)
    head_t.translate(FreeCAD.Vector(W + NECK_D, D / 2, 0))
    tab = neck_t.fuse(head_t)

    # Puzzle yuvası: sol yüzden içeri girer, sol komşunun dişini alır
    neck_b = Part.makeBox(NECK_D + TAB_TOL, NECK_W + 2 * TAB_TOL, H)
    neck_b.translate(FreeCAD.Vector(0, (D - NECK_W) / 2 - TAB_TOL, 0))
    head_b = Part.makeCylinder(HEAD_R + TAB_TOL, H)
    head_b.translate(FreeCAD.Vector(NECK_D, D / 2, 0))
    blank = neck_b.fuse(head_b)

    return base.fuse(strip).fuse(tab).cut(blank)


for i, prop in enumerate(PROPERTIES):
    tile = make_tile_shape()
    tile.translate(FreeCAD.Vector(i * (W + 5), 0, 0))

    obj = doc.addObject("Part::Feature", f"AcikMavi_{i+1:02d}_{prop['name']}")
    obj.Shape = tile
    obj.ViewObject.ShapeColor  = GROUP_COLOR
    obj.ViewObject.DisplayMode = "Shaded"

doc.recompute()
FreeCADGui.activeDocument().activeView().viewIsometric()
FreeCADGui.SendMsgToActiveView("ViewFit")
doc.saveAs(os.path.expanduser("~/monopoly_group_02_acik_mavi.FCStd"))
print("✅ Grup 02 AÇIK MAVİ tamamlandı: Aspendos, Perge, Side")

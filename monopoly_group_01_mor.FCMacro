# =============================================================
# MONOPOLY TÜRKİYE - Grup 01: MOR (Neolitik Medeniyetler)
# Çatalhöyük | Divriği Ulu Camii
# FreeCad Macro - Macro > Execute Macro ile çalıştırın
# =============================================================

import FreeCAD, Part, FreeCADGui, os

# --- Boyutlar ---
W, D, H     = 40.0, 40.0, 4.0
SW, SD, SH  = 40.0, 8.0, 6.0
NECK_W  = 8.0    # puzzle boyun genişliği (mm)
NECK_D  = 5.0    # puzzle boyun derinliği (mm)
HEAD_R  = 5.5    # puzzle kafa yarıçapı (mm)
TAB_TOL = 0.2    # yuva toleransı (mm/taraf)

GROUP_COLOR = (0.55, 0.0, 0.55)  # Mor

PROPERTIES = [
    {
        "name": "Catalhoyuk",     # Çatalhöyük
        "label": "Çatalhöyük",
        "konum": "Konya",
        "fiyat": 60,
        "kiralar": [2, 10, 30, 90, 160, 250],
        "ipotek": 30,
        "ev_maliyeti": 50,
    },
    {
        "name": "Divrigi",        # Divriği Ulu Camii
        "label": "Divriği Ulu C.",
        "konum": "Sivas",
        "fiyat": 60,
        "kiralar": [4, 20, 60, 180, 320, 450],
        "ipotek": 30,
        "ev_maliyeti": 50,
    },
]

doc = FreeCAD.newDocument("MonopolyGrup01_Mor")


def make_tile_shape():
    base  = Part.makeBox(W, D, H)
    strip = Part.makeBox(SW, SD, SH)
    strip.translate(FreeCAD.Vector(0, D - SD, H))

    # Puzzle dişi: sağ yüzden (+X) çıkar, komşu kareye kilitlenir
    neck_t = Part.makeBox(NECK_D, NECK_W, H)
    neck_t.translate(FreeCAD.Vector(W, (D - NECK_W) / 2, 0))
    head_t = Part.makeCylinder(HEAD_R, H)
    head_t.translate(FreeCAD.Vector(W + NECK_D, D / 2, 0))
    tab = neck_t.fuse(head_t)

    # Puzzle yuvası: sol yüzden içeri girer, sol komşunun dişini alır
    neck_b = Part.makeBox(NECK_D + TAB_TOL, NECK_W + 2 * TAB_TOL, H)
    neck_b.translate(FreeCAD.Vector(0, (D - NECK_W) / 2 - TAB_TOL, 0))
    head_b = Part.makeCylinder(HEAD_R + TAB_TOL, H)
    head_b.translate(FreeCAD.Vector(NECK_D, D / 2, 0))
    blank = neck_b.fuse(head_b)

    return base.fuse(strip).fuse(tab).cut(blank)


for i, prop in enumerate(PROPERTIES):
    tile = make_tile_shape()
    tile.translate(FreeCAD.Vector(i * (W + 5), 0, 0))

    obj = doc.addObject("Part::Feature", f"Mor_{i+1:02d}_{prop['name']}")
    obj.Shape = tile
    obj.ViewObject.ShapeColor  = GROUP_COLOR
    obj.ViewObject.DisplayMode = "Shaded"

doc.recompute()
FreeCADGui.activeDocument().activeView().viewIsometric()
FreeCADGui.SendMsgToActiveView("ViewFit")
doc.saveAs(os.path.expanduser("~/monopoly_group_01_mor.FCStd"))
print("✅ Grup 01 MOR tamamlandı: Çatalhöyük, Divriği Ulu Camii")

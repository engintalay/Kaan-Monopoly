# =============================================================
# MONOPOLY TÜRKİYE - Özel Kareler
# Şans ×3 | Topluluk Fonu ×3 | Gelir Vergisi | Lüks Vergisi
# Elektrik (Boğaz Köprüsü) | Su (İpek Yolu)
# FreeCad Macro - Macro > Execute Macro ile çalıştırın
# =============================================================

import FreeCAD, Part, FreeCADGui, os

W, D, H  = 40.0, 40.0, 4.0
NECK_W  = 8.0
NECK_D  = 5.0
HEAD_R  = 5.5
TAB_TOL = 0.2

OZEL_KARELER = [
    {"name": "Sans_1",        "label": "Şans",          "color": (1.0, 0.65, 0.0)},
    {"name": "Sans_2",        "label": "Şans",          "color": (1.0, 0.65, 0.0)},
    {"name": "Sans_3",        "label": "Şans",          "color": (1.0, 0.65, 0.0)},
    {"name": "TopFonu_1",     "label": "Topluluk F.",   "color": (0.4, 0.7, 1.0)},
    {"name": "TopFonu_2",     "label": "Topluluk F.",   "color": (0.4, 0.7, 1.0)},
    {"name": "TopFonu_3",     "label": "Topluluk F.",   "color": (0.4, 0.7, 1.0)},
    {"name": "GelirVergisi",  "label": "Gelir Vergisi", "color": (0.6, 0.6, 0.6)},
    {"name": "LuksVergisi",   "label": "Lüks Vergisi",  "color": (0.6, 0.6, 0.6)},
    {"name": "Elektrik",      "label": "Boğaz Köprüsü", "color": (1.0, 0.95, 0.4)},
    {"name": "Su",            "label": "İpek Yolu",     "color": (0.5, 0.85, 1.0)},
]

doc = FreeCAD.newDocument("MonopolyOzelKareler")


def make_tile_shape():
    base = Part.makeBox(W, D, H)

    # Puzzle dişi: sağ yüzden (+X) çıkar
    neck_t = Part.makeBox(NECK_D, NECK_W, H)
    neck_t.translate(FreeCAD.Vector(W, (D - NECK_W) / 2, 0))
    head_t = Part.makeCylinder(HEAD_R, H)
    head_t.translate(FreeCAD.Vector(W + NECK_D, D / 2, 0))
    tab = neck_t.fuse(head_t)

    # Puzzle yuvası: sol yüzden içeri girer
    neck_b = Part.makeBox(NECK_D + TAB_TOL, NECK_W + 2 * TAB_TOL, H)
    neck_b.translate(FreeCAD.Vector(0, (D - NECK_W) / 2 - TAB_TOL, 0))
    head_b = Part.makeCylinder(HEAD_R + TAB_TOL, H)
    head_b.translate(FreeCAD.Vector(NECK_D, D / 2, 0))
    blank = neck_b.fuse(head_b)

    return base.fuse(tab).cut(blank)


COLS = 5  # Her satırda 5 kare
for i, kare in enumerate(OZEL_KARELER):
    tile = make_tile_shape()

    row = i // COLS
    col = i % COLS
    tile.translate(FreeCAD.Vector(col * (W + 5), row * (D + 5), 0))

    obj = doc.addObject("Part::Feature", f"Ozel_{i+1:02d}_{kare['name']}")
    obj.Shape = tile
    obj.ViewObject.ShapeColor  = kare["color"]
    obj.ViewObject.DisplayMode = "Shaded"

doc.recompute()
FreeCADGui.activeDocument().activeView().viewIsometric()
FreeCADGui.SendMsgToActiveView("ViewFit")
doc.saveAs(os.path.expanduser("~/monopoly_ozel_kareler.FCStd"))
print("✅ Özel kareler tamamlandı: Şans ×3, Topluluk Fonu ×3, Vergiler, Kamu Hizmetleri")
